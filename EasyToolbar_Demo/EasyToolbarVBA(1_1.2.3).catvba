Attribute VB_Name = "ModuleDemo1"


Sub ShowCATDocumentName()
    
    MsgBox CATIA.ActiveDocument.Name

End Sub

Attribute VB_Name = "ModuleDemo2"

'AI-generated code, only Step8 added..


' CATIA VBA Macro: Language-Agnostic Simple Cube (10x10x10mm)
' Final Fix: Avoid "IsGeometricalSet" (use PartBody = Bodies(1) - fixed rule for all CATIA V5)
' Compatibility: All CATIA V5 versions/languages (English/Chinese/French/German/R20-R32)
Sub CreateSimpleCube()
    ' Step 1: Initialize CATIA object (native to CATIA VBA, no GetObject)
    Dim oCATIA As Object
    Set oCATIA = CATIA
    
    ' Step 2: Create new Part document (fixed API parameter)
    Dim oPartDoc As Object
    Set oPartDoc = oCATIA.Documents.Add("Part")
    Dim oPart As Object
    Set oPart = oPartDoc.Part
    
    ' Step 3: Get PartBody (ULTIMATE FIX: PartBody = 1st item in Bodies collection)
    ' Rule: PartBody is ALWAYS the 1st element (index 1) in Bodies (1-based indexing)
    Dim oPartBody As Object
    On Error Resume Next ' Suppress error if Bodies is empty (extremely rare)
    Set oPartBody = oPart.Bodies.Item(1)
    On Error GoTo 0
    
    ' Critical: Check if PartBody was found (defensive check)
    If oPartBody Is Nothing Then
        MsgBox "PartBody not found! Macro exited.", vbCritical, "Error"
        Exit Sub
    End If
    
    ' Step 4: Create sketch on XY Plane (fixed internal property - no language dependency)
    Dim oSketch As Object
    Set oSketch = oPartBody.Sketches.Add(oPart.OriginElements.PlaneXY)
    
    ' Step 5: Open sketch & draw 10mm square (center at origin)
    oPart.InWorkObject = oSketch
    Dim oFactory2D As Object
    Set oFactory2D = oSketch.OpenEdition()
    
    ' Draw closed square (10mm side: -5,-5 to 5,5) - pure numeric logic (no strings)
    Dim oLine1 As Object, oLine2 As Object, oLine3 As Object, oLine4 As Object
    Set oLine1 = oFactory2D.CreateLine(-5, -5, 5, -5)  ' Bottom line
    Set oLine2 = oFactory2D.CreateLine(5, -5, 5, 5)    ' Right line
    Set oLine3 = oFactory2D.CreateLine(5, 5, -5, 5)    ' Top line
    Set oLine4 = oFactory2D.CreateLine(-5, 5, -5, -5)  ' Left line
    
    ' Step 6: Close sketch & extrude to 10mm cube (pad feature)
    oSketch.CloseEdition
    Dim oPad As Object
    Set oPad = oPart.ShapeFactory.AddNewPad(oSketch, 10) ' 10mm extrusion height
    
    ' Step 7: Update part to apply all changes
    oPart.Update
    
    ' Step 8
    Set specsAndGeomWindow1 = CATIA.ActiveWindow
    Set viewer3D1 = specsAndGeomWindow1.ActiveViewer
    viewer3D1.Reframe
    Set viewpoint3D1 = viewer3D1.Viewpoint3D
    
    ' Step 9 Success message
    MsgBox "10x10x10mm cube created successfully!" & vbCrLf & _
           "Compatible with all CATIA versions/languages (no string dependencies).", vbInformation, "Success"
           
End Sub

Attribute VB_Name = "ModuleDemo3"


'CATIA macro-recorder code, only a MsgBox added.

Sub CreateBox()

MsgBox "This demo only runs in an English-language CATIA environment because the macro was recorded in English, and CATIA macro code is language-dependent."


Dim documents1 As Documents
Set documents1 = CATIA.Documents

Dim partDocument1 As PartDocument
Set partDocument1 = documents1.Add("Part")

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements

Dim reference1 As Reference
Set reference1 = originElements1.PlaneXY

Dim sketch1 As Sketch
Set sketch1 = sketches1.Add(reference1)

Dim arrayOfVariantOfDouble1(8)
arrayOfVariantOfDouble1(0) = 0#
arrayOfVariantOfDouble1(1) = 0#
arrayOfVariantOfDouble1(2) = 0#
arrayOfVariantOfDouble1(3) = 1#
arrayOfVariantOfDouble1(4) = 0#
arrayOfVariantOfDouble1(5) = 0#
arrayOfVariantOfDouble1(6) = 0#
arrayOfVariantOfDouble1(7) = 1#
arrayOfVariantOfDouble1(8) = 0#
Set sketch1Variant = sketch1
sketch1Variant.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As Axis2D
Set axis2D1 = geometricElements1.Item("AbsoluteAxis")

Dim line2D1 As Line2D
Set line2D1 = axis2D1.GetItem("HDirection")

line2D1.ReportName = 1

Dim line2D2 As Line2D
Set line2D2 = axis2D1.GetItem("VDirection")

line2D2.ReportName = 2

Dim point2D1 As Point2D
Set point2D1 = factory2D1.CreatePoint(-100#, 50#)

point2D1.ReportName = 3

Dim point2D2 As Point2D
Set point2D2 = factory2D1.CreatePoint(100#, 50#)

point2D2.ReportName = 4

Dim line2D3 As Line2D
Set line2D3 = factory2D1.CreateLine(-100#, 50#, 100#, 50#)

line2D3.ReportName = 5

line2D3.StartPoint = point2D1

line2D3.EndPoint = point2D2

Dim point2D3 As Point2D
Set point2D3 = factory2D1.CreatePoint(100#, -50#)

point2D3.ReportName = 6

Dim line2D4 As Line2D
Set line2D4 = factory2D1.CreateLine(100#, 50#, 100#, -50#)

line2D4.ReportName = 7

line2D4.EndPoint = point2D2

line2D4.StartPoint = point2D3

Dim point2D4 As Point2D
Set point2D4 = factory2D1.CreatePoint(-100#, -50#)

point2D4.ReportName = 8

Dim line2D5 As Line2D
Set line2D5 = factory2D1.CreateLine(100#, -50#, -100#, -50#)

line2D5.ReportName = 9

line2D5.StartPoint = point2D3

line2D5.EndPoint = point2D4

Dim line2D6 As Line2D
Set line2D6 = factory2D1.CreateLine(-100#, -50#, -100#, 50#)

line2D6.ReportName = 10

line2D6.EndPoint = point2D4

line2D6.StartPoint = point2D1

Dim constraints1 As Constraints
Set constraints1 = sketch1.Constraints

Dim reference2 As Reference
Set reference2 = part1.CreateReferenceFromObject(line2D3)

Dim reference3 As Reference
Set reference3 = part1.CreateReferenceFromObject(line2D1)

Dim constraint1 As Constraint
Set constraint1 = constraints1.AddBiEltCst(catCstTypeHorizontality, reference2, reference3)

constraint1.Mode = catCstModeDrivingDimension

Dim reference4 As Reference
Set reference4 = part1.CreateReferenceFromObject(line2D5)

Dim reference5 As Reference
Set reference5 = part1.CreateReferenceFromObject(line2D1)

Dim constraint2 As Constraint
Set constraint2 = constraints1.AddBiEltCst(catCstTypeHorizontality, reference4, reference5)

constraint2.Mode = catCstModeDrivingDimension

Dim reference6 As Reference
Set reference6 = part1.CreateReferenceFromObject(line2D4)

Dim reference7 As Reference
Set reference7 = part1.CreateReferenceFromObject(line2D2)

Dim constraint3 As Constraint
Set constraint3 = constraints1.AddBiEltCst(catCstTypeVerticality, reference6, reference7)

constraint3.Mode = catCstModeDrivingDimension

Dim reference8 As Reference
Set reference8 = part1.CreateReferenceFromObject(line2D6)

Dim reference9 As Reference
Set reference9 = part1.CreateReferenceFromObject(line2D2)

Dim constraint4 As Constraint
Set constraint4 = constraints1.AddBiEltCst(catCstTypeVerticality, reference8, reference9)

constraint4.Mode = catCstModeDrivingDimension

sketch1.CloseEdition

part1.InWorkObject = sketch1

part1.Update

Dim shapeFactory1 As ShapeFactory
Set shapeFactory1 = part1.ShapeFactory

Dim pad1 As Pad
Set pad1 = shapeFactory1.AddNewPad(sketch1, 20#)

part1.Update

Dim specsAndGeomWindow1 As SpecsAndGeomWindow
Set specsAndGeomWindow1 = CATIA.ActiveWindow

specsAndGeomWindow1.WindowState = catWindowStateMaximized

End Sub
